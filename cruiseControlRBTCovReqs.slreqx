# cruiseControlRBTCovReqs

## SET_SPEED: SET button locks set speed (Functional)
The cruise control shall set the target speed to the current speed when the Set button is pressed.

## BRAKE: BRAKE disengages cruise control (Functional)
The cruise control shall deactivate when a braking event has been detected.

## ACTIVATE: ACTIVATE cruise control when enabled, speed set, and no brake (Functional)
The cruise control shall activate when enabled, the Set button is pressed, and the brake is not engaged.

## INCREMENT: INCREMENT button increases set speed (Functional)
The cruise control shall increase the target speed when the Increment button is pressed.

## DECREMENT: DECREMENT button decreases set speed (Functional)
The cruise control shall decrease the target speed when the Decrement button is pressed.

## THROTTLE: THROTTLE applied smoothly if speed differs from target (Functional)
The cruise control shall limit throttle rate of change to +/- 1 radian per second.
