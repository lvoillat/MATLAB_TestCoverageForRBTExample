# LiveDoc_Polarion-LVO_Matlab_Requirements_Cruise Control

## http://pl1chzrh0298nb/polarion/#/project/Matlab/wiki/Requirements/Cruise Control: References to Cruise Control (Container)
Read-only references to Polarion document.

### MATL-791: Cruise Control (Container)

#### MATL-777: Active Control (Container)

##### MATL-780: The system shall actively control the vehicle's speed to maintain the desired ta... (Functional)
The system shall actively control the vehicle's speed to maintain the desired target speed.

##### MATL-787: The system shall be able to accelerate or decelerate the vehicle as needed to re... (Functional)
The system shall be able to accelerate or decelerate the vehicle as needed to reach and maintain the target speed.

#### MATL-772: Target Speed: (Container)

##### MATL-782: The system shall allow the user to set a target speed for the vehicle. (Functional)

##### MATL-784: The system shall maintain the vehicle's speed at the user-specified target speed... (Functional)
The system shall maintain the vehicle's speed at the user-specified target speed.

#### MATL-774: Previous Target: (Container)

##### MATL-781: The system shall store the previous target speed set by the user. (Functional)

##### MATL-776: The system shall be able to revert to the previous target speed if needed. (Functional)

#### MATL-783: Active Last Step: (Container)

##### MATL-778: The system shall keep track of the last active control step, including the magni... (Functional)
The system shall keep track of the last active control step, including the magnitude and direction of the control action.

##### MATL-773: The system shall be able to reference the active last step for feedback and adju... (Functional)
The system shall be able to reference the active last step for feedback and adjustment of the control algorithm.

#### MATL-785: PI Controller: (Container)

##### MATL-775: The system shall use a Proportional-Integral (PI) controller to regulate the veh... (Functional)
The system shall use a Proportional-Integral (PI) controller to regulate the vehicle's speed.

##### MATL-788: The PI controller shall use the difference between the target speed and the actu... (Functional)
The PI controller shall use the difference between the target speed and the actual vehicle speed as the error signal.

##### MATL-789: The PI controller shall adjust the throttle or braking input to the vehicle to m... (Functional)
The PI controller shall adjust the throttle or braking input to the vehicle to minimize the speed error.

#### MATL-779: Control Active: (Container)

##### MATL-790: The system shall have a clear indication of when the cruise control is actively... (Functional)
The system shall have a clear indication of when the cruise control is actively controlling the vehicle's speed.

##### MATL-786: The system shall provide a way for the user to engage and disengage the cruise c... (Functional)
The system shall provide a way for the user to engage and disengage the cruise control as needed.
