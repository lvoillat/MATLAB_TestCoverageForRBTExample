# LiveDoc_Polarion-LVO_Simulink_Requirements_Cruise Control

## http://pl1chzrh0298nb/polarion/#/project/Simulink/wiki/Requirements/Cruise Control: References to Cruise Control (Container)
Read-only references to Polarion document.

### SIMU-546: Cruise Control (Container)

#### SIMU-528: Active Control (Container)

##### SIMU-540: The system shall actively control the vehicle's speed to maintain the desired ta... (Functional)
The system shall actively control the vehicle's speed to maintain the desired target speed.

##### SIMU-539: The system shall be able to accelerate or decelerate the vehicle as needed to re... (Functional)
The system shall be able to accelerate or decelerate the vehicle as needed to reach and maintain the target speed.

#### SIMU-527: Target Speed (Container)

##### SIMU-531: The system shall allow the user to set a target speed for the vehicle. (Functional)

##### SIMU-534: The system shall maintain the vehicle's speed at the user-specified target speed... (Functional)
The system shall maintain the vehicle's speed at the user-specified target speed.

#### SIMU-530: Previous Target (Container)

##### SIMU-533: The system shall store the previous target speed set by the user. (Functional)

##### SIMU-543: The system shall be able to revert to the previous target speed if needed. (Functional)

#### SIMU-529: Active Last Step (Container)

##### SIMU-542: The system shall keep track of the last active control step, including the magni... (Functional)
The system shall keep track of the last active control step, including the magnitude and direction of the control action.

##### SIMU-545: The system shall be able to reference the active last step for feedback and adju... (Functional)
The system shall be able to reference the active last step for feedback and adjustment of the control algorithm.

#### SIMU-537: PI Controller (Container)

##### SIMU-544: The system shall use a Proportional-Integral (PI) controller to regulate the veh... (Functional)
The system shall use a Proportional-Integral (PI) controller to regulate the vehicle's speed.

##### SIMU-538: The PI controller shall use the difference between the target speed and the actu... (Functional)
The PI controller shall use the difference between the target speed and the actual vehicle speed as the error signal.

##### SIMU-535: The PI controller shall adjust the throttle or braking input to the vehicle to m... (Functional)
The PI controller shall adjust the throttle or braking input to the vehicle to minimize the speed error.

#### SIMU-536: Control Active (Container)

##### SIMU-541: The system shall have a clear indication of when the cruise control is actively... (Functional)
The system shall have a clear indication of when the cruise control is actively controlling the vehicle's speed.

##### SIMU-532: The system shall provide a way for the user to engage and disengage the cruise c... (Functional)
The system shall provide a way for the user to engage and disengage the cruise control as needed.
